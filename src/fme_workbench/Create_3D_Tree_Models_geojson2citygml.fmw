FME workspace Create_3D_Tree_Models_geojson2citygml.fmw
Title: Parameterized 3D tree modeling for CityGML SolitaryVegetationObjects
Description: Creates CityGML SolitaryVegetationObjects from parameterized tree positions and prototype tree models. 
3D tree models are created using space-efficient implicit modeling. 
Therefore the geometry of each tree model is stored only once and represented by an anchor point and a transformation matrix that unfolds the trees shape at the given positions.

Parameters:
- SourceDataset_GEOJSON =   # GeoJSON with parametrized tree positions
- SourceDataset_SKP =   # Prototypic tree models
- DestDataset_CITYGML =   # Destination CityGML Document

Readers:
- SKP_1: SKP from $(SourceDataset_SKP)
- GEOJSON_1: GEOJSON from $(SourceDataset_GEOJSON)

Writers:
- CITYGML_1: CITYGML to $(DestDataset_CITYGML)

Note: Select all models as input
Note: Workspace description / Creates CityGML SolitaryVegetationObjects from parameterized tree positions and prototype tree models. / 3D tree models are created using space-efficient implicit modeling. / Therefore the geometry of each tree model is stored only once and represented by an anchor point and a transformation matrix that unfolds the trees shape at the given positions. / Source data / tree positions: / - GeoJSON containing parameterized tree positions as points / - tree height, crown diameter and x,y,z coordinates are mandatory / - for modelling as ellipsoids width, height and orientation of tree crown are needed / tree models: / - Sketchup files with normalized prototypes / - height and diameter of each model are always 1 m which allows scaling via the transformation matrix / - models differ in their ration between crown height and trunk height
Note: Merge parameterized tree positions with corresponding tree models
FeatureMerger_2
    ATTR_ACCUM_MODE = Merge Supplier
    ATTR_CONFLICT_RES = Use Requestor
    IGNORE_NULLS = No
    JOIN_KEYS = @Value(tree_model) @Value(fme_feature_type) AUTO
    MERGE_TYPE = Attributes and Geometry
    PROCESS_DUPS = NO
    REJECT_NULL_MISSING_KEYS = No
    SUPPLIERS_FIRST = No
    MERGED -> VertexCreator_2

Bookmark: Parameterized Tree Positions
tree_positions_parameterized (reader GEOJSON_1)
    attributes: treeID int, treeID_ioer string, h_tree float, h_crown float, d_crown float, h_trunk float, X float, Y float, Z float, ch_width float, ch_length float, ch_orientation float, ch_area float, tree_model string, crownvolume float, crownsurface float, n_pulses float, mean_nor float, mean_ndvi float, z_max float, z_min float, z_mean float, z_std float, zq1 float, zq2 float, zq5 float, zq95 float, zq99 float
    -> GeometryRemover

Bookmark: Prepare implicit modelling parameters
GeometryRemover
    -> AttributeManager
AttributeManager
    ATTR_TABLE:
      REMOVE treeID
      RENAME_SET_VALUE treeID_ioer > gml_id
      REMOVE ch_area
      REMOVE crownvolume
      REMOVE crownsurface
      REMOVE n_pulses
      REMOVE mean_nor
      REMOVE mean_ndvi
      REMOVE z_max
      REMOVE z_min
      REMOVE z_mean
      REMOVE z_std
      REMOVE zq1
      REMOVE zq2
      REMOVE zq5
      REMOVE zq95
      REMOVE zq99
    -> AttributeCreator
Note: Calculate rotation and scaling for each crown
AttributeCreator
    ATTR_TABLE:
      SET_TO Sx = @Value(ch_length)
      SET_TO Sy = @Value(ch_width)
      SET_TO cosPhi = @Evaluate(@cos(@Value(ch_orientation)))
      SET_TO sinPhi = @Evaluate(@sin(@Value(ch_orientation)))
      SET_TO m_sinPhi = @Evaluate(-1*@Value(sinPhi))
      SET_TO M11 = @Evaluate(@Value(cosPhi)*@Value(Sx))
      SET_TO M12 = @Evaluate(@Value(m_sinPhi)*@Value(Sy))
      SET_TO M21 = @Evaluate(@Value(sinPhi)*@Value(Sx))
      SET_TO M22 = @Evaluate(@Value(cosPhi)*@Value(Sy))
    -> FeatureMerger_2 [REQUESTOR]

Bookmark: Tree Model Prototypes
crown_1_trunk_9 (reader SKP_1)
    -> AttributeCreator_2

Bookmark: Prepare geometry instances
AttributeCreator_2
    ATTR_TABLE = SET_TO tree_model_id = tree_prototype_@Count(1)
    -> GeometryPropertySetter_2
GeometryPropertySetter_2
    GQUERY:
      for $geom in //geometry
      where $geom/count(parent::geometry) = 0
      return number($geom/@fme_id)
    OVERWRITE_CHOICE = No
    REMOVE_ATTRIBUTE = No
    SETTYPE_PARAM = Traits From Attributes
    SRC_ATTRS = tree_model_id
    SET -> SharedItemAdder
SharedItemAdder
    REF_ATTR = _shared_item_id
    SHARED_TYPE = Geometry Definition
    STORAGE_MODE = Add New Item
    -> GeometryRemover_2
GeometryRemover_2
    -> FeatureMerger_2 [SUPPLIER]

Bookmark: Create anchor points and set geometry instances
Note: Create anchor point to unfold geometry at tree positions
VertexCreator_2
    MEASURE_TYPE = Continuous
    MODE_NAME = Replace with Point
    XVAL = @Value(X)
    YVAL = @Value(Y)
    ZVAL = @Value(Z)
    -> SharedItemIDSetter_2
Note: Create geometry instances
SharedItemIDSetter_2
    REFERENCE_ATTRIBUTE = _shared_item_id
    SHARED_TYPE = Geometry Definition
    STORAGE_MODE = From Attribute
    -> AttributeManager_2

Bookmark: Create CityGML specific attributes
Note: Define transformation matrix (scale, offset, rotation)
AttributeManager_2
    ATTR_TABLE:
      SET_TO citygml_lod_name = lod2ImplicitRepresentation
      SET_TO citygml_level_of_detail = 2
      SET_TO citygml_transformation_matrix = @Value(M11) @Value(M12) 0.0 0.0
        @Value(M21) @Value(M22) 0.0 0.0
        0.0 0.0 @Value(h_tree) 0.0
        0.0 0.0 0.0 1.0
      RENAME_SET_VALUE h_tree > citygml_height = @Value(citygml_height)
      SET_TO citygml_height_units = m
      RENAME_SET_VALUE d_crown > citygml_crown_diameter = @Value(citygml_crown_diameter)
      SET_TO citygml_crown_diameter_units = m
      REMOVE Sx
      REMOVE Sy
      REMOVE cosPhi
      REMOVE sinPhi
      REMOVE m_sinPhi
      REMOVE M11
      REMOVE M12
      REMOVE M21
      REMOVE M22
      REMOVE ch_width
      REMOVE ch_length
      REMOVE ch_orientation
      REMOVE tree_model
      REMOVE tree_model_id
      REMOVE fme_feature_type
      REMOVE _shared_item_id
    -> GeometryPropertySetter
GeometryPropertySetter
    GQUERY:
      for $geom in //geometry
      where $geom/count(parent::geometry) = 0
      return number($geom/@fme_id)
    OVERWRITE_CHOICE = No
    REMOVE_ATTRIBUTE = No
    SETTYPE_PARAM = Traits From Attributes
    SRC_ATTRS = citygml_level_of_detail citygml_height Z citygml_crown_diameter_units citygml_transformation_matrix citygml_crown_diameter citygml_height_units gml_id citygml_lod_name X Y h_crown h_trunk
    SET -> SolitaryVegetationObject (writer CITYGML_1)

Bookmark: Write to destination schema
Note: General Parameters: / Writer Type: OGC CityGML / Feature Type Name: SolitaryVegetationObject / Writer: <not set> [CITYGML] / Allowed Geometries: All / Exposed Attributes: NameTypegml_idxml_buffercitygml_lod_namexml_char(200)citygml_level_of_detailxml_char(200)citygml_transformation_matrixxml_char(200)citygml_heightxml_real64citygml_height_unitsxml_char(200)citygml_crown_diameterxml_real64citygml_crown_diameter_unitsxml_char(200)h_crownxml_real64h_trunkxml_real64Xxml_real64Yxml_real64Zxml_real64
SolitaryVegetationObject (writer CITYGML_1)
    attributes: citygml_height xml_real64, citygml_height_units xml_char(200), citygml_crown_diameter xml_real64, citygml_crown_diameter_units xml_char(200), h_crown xml_real64, h_trunk xml_real64, X xml_real64, Y xml_real64, Z xml_real64
